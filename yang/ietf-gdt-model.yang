module ietf-gdt-model {
  yang-version 1.1;
  namespace "urn:ietf:params:xml:ns:yang:ietf-gdt-model";
  prefix gdtm;

  import ietf-inet-types {
    prefix inet;
    reference
      "RFC 6991: Common YANG Data Types";
  }
  import ietf-yang-structure-ext {
    prefix sx;
    reference
      "RFC 8525: YANG Data Structure Extensions";
  }
  import ietf-yang-types {
    prefix yang;
    reference
      "RFC 6991: Common YANG Data Types";
  }
  import ietf-datastores {
    prefix ds;
    reference
      "RFC 8342: Network Management Datastore Architecture (NMDA)";
  }

  organization
    "IETF GREEN (Getting Ready for Energy-Efficient Networking) Working Group";
  contact
    "WG Web:  <https:/datatracker.ietf.org/wg/green/>
     WG List: <mailto:green@ietf.org>

     TODO - Replace this :-)
     Author:  Robert Wilton
              <mailto:rwilton@cisco.com>";
  description
    "This is an example working YANG module to help discuss issues.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.

     Copyright (c) 2025 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.";

  revision 2025-10-06 {
    description
      "Initial revision.";
    reference
      "XXXX: IETF GREEN Design Work";
  }

  /*
   * FEATURES
   */

  /*
   * IDENTITIES
   */

  /*
   * TYPEDEFs
   */

  /*
   * GROUPINGS
   */

  /*
   * RPCs
   */

  rpc clear-metrics {
    description
      "Example RPC to clear collected metrics information";
    input {
      leaf metric {
        type string;
        mandatory true;
        description
          "The hypothetical metric to clear";
      }
    }
  }

  /*
   * NOTIFICATIONS
   */

  /*
   * DATA NODES
   */

  container model-example-1 {
    description
      "Example data model 1";
  }

  container model-example-2 {
    description
      "Example data model 2";
  }

}
